AGENTX-TUTORIAL-MIB DEFINITIONS ::= BEGIN

IMPORTS
    NOTIFICATION-GROUP, OBJECT-GROUP
        FROM SNMPv2-CONF
    DisplayString
        FROM SNMPv2-TC
    experimental, OBJECT-TYPE, NOTIFICATION-TYPE, Integer32, MODULE-IDENTITY
        FROM SNMPv2-SMI
;

--
-- top level structure
--
agentxTutorial MODULE-IDENTITY
    LAST-UPDATED "201701050000Z"
    ORGANIZATION "theunixtips"
    CONTACT-INFO
         "Vishal Jain
	  kunwarv my last name at gmail
	  firstname.lastname at theunixtips"
    DESCRIPTION
         "Example MIB to show how to make use of net-snmp
	  agentx library step-by-step"
    REVISION     "201701050000Z"
    DESCRIPTION  "First step with Read-Only Scalars"
    ::= { experimental 9999 }

myScalars              OBJECT IDENTIFIER ::= { agentxTutorial  1 }
myTables               OBJECT IDENTIFIER ::= { agentxTutorial  2 }
myNotifications        OBJECT IDENTIFIER ::= { agentxTutorial  0 }
myNotificationObjects  OBJECT IDENTIFIER ::= { myNotifications 0 }
myConformenceGroups    OBJECT IDENTIFIER ::= { agentxTutorial 99 }

---
--- Some Scalars
---
myROString OBJECT-TYPE
    SYNTAX      DisplayString
    MAX-ACCESS  read-only
    STATUS      current
    DESCRIPTION "A string value for tutorial"
    ::= { myScalars 1 }

myROInteger OBJECT-TYPE
    SYNTAX      Integer32 (0..2147483647)
    MAX-ACCESS  read-only
    STATUS      current
    DESCRIPTION "An integer value for tutorial"
    ::= { myScalars 2 }

---
--- A test table
---
myTestTable OBJECT-TYPE
    SYNTAX      SEQUENCE OF MyTestTableEntry
    MAX-ACCESS  not-accessible
    STATUS      current
    DESCRIPTION "A test table with few columns and rows"
    ::= { myTables 1 }

myTestTableEntry OBJECT-TYPE
    SYNTAX      MyTestTableEntry
    MAX-ACCESS  not-accessible
    STATUS      current
    DESCRIPTION "A row of data in myTestTable"
    INDEX       { myROStringCol1 }
    ::= { myTestTable 1 }

MyTestTableEntry ::= SEQUENCE {
    myROStringCol1 DisplayString,
    myROIntCol2    Integer32
}

myROStringCol1 OBJECT-TYPE
    SYNTAX      DisplayString
    MAX-ACCESS  read-only
    STATUS      current
    DESCRIPTION "Just a test label for table"
    ::= { myTestTableEntry 1 }

myROIntCol2 OBJECT-TYPE
    SYNTAX      Integer32 (0..2147483647)
    MAX-ACCESS  read-only
    STATUS      current
    DESCRIPTION "Just a test integer for table"
    ::= { myTestTableEntry 2 }

---
--- Notifications/Traps
---
myTrapTime OBJECT-TYPE
    SYNTAX      Integer32
    MAX-ACCESS  accessible-for-notify
    STATUS      current
    DESCRIPTION "trap time stamp"
    ::= { myNotificationObjects 1 }

myTrapData OBJECT-TYPE
    SYNTAX      DisplayString
    MAX-ACCESS  accessible-for-notify
    STATUS      current
    DESCRIPTION "trap data"
    ::= { myNotificationObjects 2 }

myROIntHit NOTIFICATION-TYPE
    OBJECTS     { myTrapData, myTrapTime, myROInteger }
    STATUS      current
    DESCRIPTION
        "Generated when ROInt variable reach certain following threshold
             myROInteger % 5 = 1
        "
    ::= { myNotifications 1 }

---
--- Conformance related definitions
---

myScalarGroup OBJECT-GROUP
    OBJECTS { myROString, myROInteger }
    STATUS      current
    DESCRIPTION
        "Group of stats that we are implementing."
    ::= { myConformenceGroups 1 }

myTableGroup OBJECT-GROUP
    OBJECTS { myROStringCol1, myROIntCol2 }
    STATUS      current
    DESCRIPTION
        "Group of table stats that we are implementing."
    ::= { myConformenceGroups 2 }

myTrapObjectGroup OBJECT-GROUP
    OBJECTS { myTrapTime, myTrapData }
    STATUS      current
    DESCRIPTION
        "Group of data points for sending Traps."
    ::= { myConformenceGroups 3 }

myTrapsGroup NOTIFICATION-GROUP
    NOTIFICATIONS { myROIntHit }
    STATUS      current
    DESCRIPTION
        "Notification indicating a specific change in interesting values."
    ::= { myConformenceGroups 4 }

---
--- vim modeline to tell it how to colorize
--- vim: syntax=mib
---
END
